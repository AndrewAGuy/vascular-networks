# ImportVessels.FCMacro
# Copyright 2021 Andrew Guy
# Licensed under AGPL v3.0

# Part of the Vascular.Networks project
# See https://github.com/AndrewAGuy/vascular-networks/
# File: Vascular.IO.Text/content/FreeCAD/ImportVessels.FCMacro

# Usage:
# Imports segments from a CSV file written using Vascular.IO.Text.SegmentCsv
# with comma (sepChar = ',', the default value) separators. 
# Each segment is of the form "x y z X Y Z r": two positions and a radius. 
# During loading, the largest segment radius attached to a node is stored,
# and spheres of this radius are created later to fill the gaps between the
# cylindrical segments.

# Installation:
# Copy to your FreeCAD macro directory:
#   From the top menu bar: Macro -> Macros ...
#   The path to the macro directory should be shown at the bottom of this
#   window. Alternatively, create a new macro and copy the text of this.

from PySide import QtGui
from FreeCAD import Base
import Part
import sys, csv

def addRow(s, S, C):
	if len(s) != 7:
		raise IndexError(
			f"Incorrect number of tokens in row: "
			f"expected 7, received {len(s)}")
	a = (float(s[0]), float(s[1]), float(s[2]))
	b = (float(s[3]), float(s[4]), float(s[5]))
	r = float(s[6])
	C.append((a, b, r))
	S[a] = max(S[a], r) if a in S else r
	S[b] = max(S[b], r) if b in S else r

def loadFile(p):
	S = dict()
	C = list()
	with open(p, newline = '') as f:
		r = csv.reader(f, delimiter = ',')
		n = 0
		try:
			for s in r:
				s = [x for x in s if x]
				n += 1
				addRow(s, S, C)
		except Exception as e:
			e.lineNum = n
			e.tokens = s
			raise
	return C, S

def addCylinder(o, a, b, r):
	A = Base.Vector(a[0], a[1], a[2])
	B = Base.Vector(b[0], b[1], b[2])
	D = B.sub(A)
	L = D.Length
	D.normalize()
	c = Part.makeCylinder(r, L, A, D)
	return c if o is None else o.fuse(c)

def addSphere(o, p, r):
	x = Base.Vector(p[0], p[1], p[2])
	s = Part.makeSphere(r, x)
	return s if o is None else o.fuse(s)

def makePart(C, S):
	o = None
	for a, b, r in C:
		o = addCylinder(o, a, b, r)
	for p, r in S.items():
		o = addSphere(o, p, r)
	return o

def getGeometry():
	fp, F = QtGui.QFileDialog.getOpenFileName(
		filter = "*.csv", 
		caption = "Import Vessels")
	return loadFile(fp)

def main():
	try:
		C, S = getGeometry()
	except (IndexError, ValueError) as e:
		print(f"In row {e.lineNum}: {type(e).__name__}")
		for a in e.args:
			print(f"\t{a}")
		print(f"Tokens: {', '.join(e.tokens)}")
		return
	except FileNotFoundError:
		return
	d = App.newDocument("")
	p = d.addObject("Part::Feature", "Vessels")
	p.Shape = makePart(C, S)

main()
